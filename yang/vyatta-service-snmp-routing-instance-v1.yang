module vyatta-service-snmp-routing-instance-v1 {
	namespace "urn:vyatta.com:mgmt:vyatta-service-snmp-routing-instance:1";
	prefix vyatta-service-snmp--routing-instance-v1;

	import vyatta-services-v1 {
		prefix service;
	}
	import configd-v1 {
		prefix configd;
	}
	import vyatta-service-snmp-v1 {
		prefix snmp;
	}
	import vyatta-routing-v1 {
		prefix vyatta-routing;
	}

	organization "AT&T Inc.";
	contact
		"AT&T
		 Postal: 208 S. Akard Street
		         Dallas, TX  75202
		 Web:    www.att.com";

	description
		"Copyright (c) 2018-2021, AT&T Intellectual Property.
		 All rights reserved.

		 Copyright (c) 2016 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 SNMP routing-instance configuration";

	revision 2021-08-04 {
		description "Support for listening on multiple VRFs.";
	}

	revision 2016-03-07 {
		description "Added support for VRF-aware SNMP.";
	}

	grouping routing-instance-group {
		leaf routing-instance {
			description "This leaf is used to associate a routing-instance with trap-target,
				     allowing VRF specific traps to be sent to specific trap receivers.";
			configd:help "Specifies the routing-instance for trap-target";
			type leafref {
				path "/vyatta-routing:routing/vyatta-routing:routing-instance/vyatta-routing:instance-name";
			}
		}
	}

	augment /service:service/snmp:snmp/snmp:trap-target {
		uses routing-instance-group {
			refine routing-instance {
				configd:help "Specifies routing-instance for SNMPv2 trap-target, default otherwise";
			}
		}
	}
	augment /service:service/snmp:snmp/snmp:community {
		leaf context {
			description "This leaf is used to map a context to SNMP v1/v2c community string.";
			configd:help "Defines the name of the routing instance";
			type leafref {
				path "/vyatta-routing:routing/vyatta-routing:routing-instance/vyatta-routing:instance-name";
			}
		}
	}
	augment /service:service/snmp:snmp/snmp:v3/snmp:trap-target {
		uses routing-instance-group {
			refine routing-instance {
				configd:help "Specifies routing-instance for SNMPv3 trap-target, default otherwise";
			}
		}
	}
	augment /service:service/snmp:snmp {
		leaf-list routing-instance {
			description "This leaf specifies the routing-instance SNMP agent is listening
				on for incoming SNMP requests.";
			must "(current() = /vyatta-routing:routing/vyatta-routing:routing-instance/vyatta-routing:instance-name) or (current() = 'default')" {
				error-message "Unknown routing instance";
			}
			configd:help "Specifies the routing-instance to listen on for SNMP requests";
			type union {
				type vyatta-routing:routing-instance-name;
				type enumeration {
					enum default;
					configd:help "Default routing instance";
				}
			}
			configd:allowed "echo -n $VAR(/routing/routing-instance/@@)";
		}
	}
	augment /service:service/snmp:snmp/snmp:listen-address {
		leaf routing-instance {
			description "This leaf is used to associate a routing-instance with listen-address,
				     allowing SNMP to listen for requests from specific VRFs.";
			configd:help "Specifies the routing-instance for listen-address";
			type leafref {
				path "/vyatta-routing:routing/vyatta-routing:routing-instance/vyatta-routing:instance-name";
			}
		}
	}
}
